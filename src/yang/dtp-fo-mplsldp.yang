module dtp-fo-mplsldp { 

  namespace "http://www.cisco.com/dtp-fo-mplsldp";
  prefix dtpn-mplsldp;

  import dtp-network { prefix dtpn; }
  import dtp-fo-link-side-logical { prefix dtplsl;}
  import ietf-inet-types { prefix inet; }
  import tailf-common { prefix tailf; }
  import tailf-ncs { prefix ncs; }

  description
    "This is an add on model to the dtp-network package/service";

  revision 2017-11-28 {
    description
      "Initial revision.";
  }

  grouping mplsldp-object-common {
    leaf disable-advertise-acl {
      type string;
    }
  }

  grouping mplsldp-object-link-side {
    leaf router-id-link-name {
      type leafref {
        path "/dtpn:dtp/dtpn:network/dtpn:topology/dtpn:link/dtpn:name";
      }
      must "deref(current())/../dtpn:side/dtpn:side-type/dtplsl:logical/dtplsl:port/dtplsl:port-type='Loopback'" {
        tailf:dependency "/dtpn:dtp/dtpn:network/dtpn:topology/dtpn:link/dtpn:side/dtpn:side-type/dtplsl:logical/dtplsl:port/dtplsl:port-type";
      }
    }
    uses mplsldp-object-common;
  }

  grouping mplsldp-object-topology {
    leaf router-id-loopback-name {
      type uint8 {
        range "0..20";
      }
    }
    uses mplsldp-object-common;
  }

  grouping mplsldp-fo {
    list mplsldp {
      key name;
      uses dtpn:function-object;
    }
  }

  augment /dtpn:dtp/dtpn:network/dtpn:topology/dtpn:function-objects {
    list mplsldp {
      max-elements 1;
      key "function-object-name";
      leaf function-object-name {
        type leafref {
          path "/dtpn:dtp/dtpn:function-object-definitions/dtpn:topology/mplsldp/name";
        }
      }
      uses mplsldp-object-topology;
    }
  }

  augment /dtpn:dtp/dtpn:network/dtpn:topology/dtpn:link/dtpn:side/dtpn:function-objects {
    list mplsldp {
      max-elements 1;
      key "function-object-name";
      leaf function-object-name {
        type leafref {
          path "/dtpn:dtp/dtpn:function-object-definitions/dtpn:link/dtpn:side/mplsldp/name";
        }
      }
      uses mplsldp-object-link-side;
    }
  }

  augment /dtpn:dtp/dtpn:function-object-definitions/dtpn:topology {
    uses mplsldp-fo;
  }

  augment /dtpn:dtp/dtpn:function-object-definitions/dtpn:link/dtpn:side {
    uses mplsldp-fo;
  }

}
